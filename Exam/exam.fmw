FME workspace exam.fmw

Parameters:
- DestDataset_POSTGIS =
- SourceDataset_GEOJSON =
- SourceDataset_GEOJSON_3 =

Readers:
- GEOJSON_1: GEOJSON from $(SourceDataset_GEOJSON)
- GEOJSON_2: GEOJSON from $(SourceDataset_GEOJSON_3)

Writers:
- POSTGIS_1: POSTGIS to $(DestDataset_POSTGIS)

FAAF01608900 (writer POSTGIS_1)
    attributes: usage1 text, vacant_a_louer text, point_count int8, fme_rejection_code text
Note: Combinaison de commerces et de zones
FeatureJoiner__Rejected_: Logger
    LOG_FEATURE = LOG_ONLY
    MAXCOORDS = 20
    MAXFEATS = 20
    MESSAGE = Feature is:
    SEVERITY = INFO

Bookmark: Couches de commerces
OCcupation commerciale 2022 (reader GEOJSON_1)
    attributes: ID string, ORIGINE string, T_COMMERCE string, DATE_RECENSEMENT string, CIVIQUE string, TYPE_VOIE string, LIEN_VOIE string, NOM_VOIE string, ORIENTATION string, ADRESSE string, SUITE string, CODE_POST string, ETAGE string, NOM_CENTRE string, NOM_ETAB string, ID_USAGE1 string, USAGE1 string, ID_USAGE2 string, USAGE2 string, ID_USAGE3 string, USAGE3 string, SCIAN string, SITEWEB string, SITE_TRANSACTIONNEL string, ACCES_MOBILITE_REDUITE string, VACANT_A_LOUER string, A_LOUER_CONTACT string, A_LOUER_TELEPHONE string, ARRONDISSEMENT string, QUARTIER string,
      SDC_NOM string, SECTEUR_PME string, ENFANT string, MULTIUSAGE string, MULTIOCCUPANT string, NEQ string, SUFFIXE_NEQ string, COORDX string, COORDY string, LAT string, LONG string
    -> PointOnAreaOverlayer [POINT]
    -> PointOnAreaOverlayer [AREA]
Note: compter le nombre de commerces vacants dans des hexagones
PointOnAreaOverlayer
    ATTR_ACCUM_MODE = Merge Incoming
    ATTR_CONFLICT_RES = Use Original
    DEAGGREGATE_INPUT = Yes
    OV_ATTR = point_count
    POLYS_FIRST = NO
    POINT -> AttributeKeeper
    <REJECTED> -> PointOnAreaOverlayer__Rejected_
AttributeKeeper
    CREATE_BULK_MODE_FEATURES = NO
    KEEP_ATTRS = point_count,USAGE1,VACANT_A_LOUER
    -> VertexCreator
Note: définir les coordonnées x et y
VertexCreator
    MEASURE_TYPE = Continuous
    MODE_NAME = Replace with Point
    XVAL = @Value(USAGE1)
    YVAL = @Value(USAGE1)
    <REJECTED> -> VertexCreator__Rejected_
VertexCreator__Rejected_: Logger
    LOG_FEATURE = LOG_ONLY
    MAXCOORDS = 20
    MAXFEATS = 20
    MESSAGE = Feature is:
    SEVERITY = INFO
    LOGGED -> FeatureJoiner [LEFT]
PointOnAreaOverlayer__Rejected_: Logger
    LOG_FEATURE = LOG_ONLY
    MAXCOORDS = 20
    MAXFEATS = 20
    MESSAGE = Feature is:
    SEVERITY = INFO

Bookmark: hexagones
limites-terrestres (reader GEOJSON_2)
    attributes: DefaultAtt string
    -> H3HexagonalIndexer
Note: le READER des hexagones
H3HexagonalIndexer
    INDEX_OPERATION = Index
    -> Reprojector
    <REJECTED> -> H3HexagonalIndexer__Rejected_
Reprojector
    DEST = EPSG:3857
    INTERPOLATION_TYPE_NAME = Nearest Neighbor
    RASTER_CELL_SIZE = Preserve Cells
    RASTER_TOLERANCE = 0.0
    REPROJECTED -> PointOnAreaOverlayer_2 [AREA]
PointOnAreaOverlayer_2
    ATTR_ACCUM_MODE = Merge Incoming
    ATTR_CONFLICT_RES = Use Original
    DEAGGREGATE_INPUT = Yes
    OV_ATTR = point_count
    POLYS_FIRST = NO
    AREA -> Dissolver__Rejected_
    <REJECTED> -> PointOnAreaOverlayer_2__Rejected_
Dissolver__Rejected_: Logger
    LOG_FEATURE = LOG_ONLY
    MAXCOORDS = 20
    MAXFEATS = 20
    MESSAGE = Feature is:
    SEVERITY = INFO
    LOGGED -> FeatureJoiner [RIGHT]
PointOnAreaOverlayer_2__Rejected_: Logger
    LOG_FEATURE = LOG_ONLY
    MAXCOORDS = 20
    MAXFEATS = 20
    MESSAGE = Feature is:
    SEVERITY = INFO
H3HexagonalIndexer__Rejected_: Logger
    LOG_FEATURE = LOG_ONLY
    MAXCOORDS = 20
    MAXFEATS = 20
    MESSAGE = Feature is:
    SEVERITY = INFO

Bookmark: New Bookmark
FeatureJoiner
    ATTR_CONFLICT_RES = Use Left
    GEOMETRY_HANDLING = Use Left
    JOIN_KEYS = point_count point_count AUTO
    JOIN_MODE = Inner
    UNJOINED_LEFT -> FAAF01608900 (writer POSTGIS_1)
    <REJECTED> -> FeatureJoiner__Rejected_
